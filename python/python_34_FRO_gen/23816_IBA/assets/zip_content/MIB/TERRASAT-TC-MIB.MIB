TERRASAT-TC-MIB DEFINITIONS ::= BEGIN

IMPORTS
    MODULE-IDENTITY
        FROM SNMPv2-SMI
	TEXTUAL-CONVENTION
		FROM SNMPv2-TC
    terrasat
        FROM TERRASAT-SMI-MIB;

terrasatTextualConventions  MODULE-IDENTITY
    LAST-UPDATED "202008200000Z"
    ORGANIZATION "Terrasat Communications, Inc."
    CONTACT-INFO
            "Address: Terrasat Communications, Inc.
             235 Vineyard Court
             Morgan Hill, CA 95037
             USA

             Tel: +1 408 782-2166

             E-mail: techsupport@terrasatinc.com"
    DESCRIPTION
            "The MIB module for textual conventions for the enterprise"
	REVISION	"202008200000Z"
	DESCRIPTION
			"Added watt350 to PowerWatts."
	REVISION	"202005060000Z"
	DESCRIPTION
			"Added watt500 to PowerWatts."
	REVISION	"201903120000Z"
	DESCRIPTION
			"Added cBandGS to FrequencyBand.
			 Added watt300,watt45,watt225 to PowerWatts."
	REVISION	"201510010000Z"
	DESCRIPTION
			"Added ArmRedundancyMode"
	REVISION	"201509220000Z"
	DESCRIPTION
			"Added watt15 to PowerWatts."
	REVISION	"201409090000Z"
	DESCRIPTION
			"Added kaBand4 to Frequency and watt400 to PowerWatts."
	REVISION	"201310160000Z"
	DESCRIPTION
			"Added TenMHzMode."
	REVISION	"201109220000Z"
	DESCRIPTION
			"Extended the meaning of AlarmState and TxMute."

	REVISION	"200909280000Z"
	DESCRIPTION
			"The initial revision."
    ::= { terrasat 4 }

OffOnValue ::= TEXTUAL-CONVENTION
	STATUS			current
	DESCRIPTION		"Off/On state variable"
	SYNTAX			INTEGER {off(0), on(1)}

NoYesValue ::= TEXTUAL-CONVENTION
	STATUS			current
	DESCRIPTION		"No/Yes state variable"
	SYNTAX			INTEGER {no(0), yes(1)}

AlarmLevel ::= TEXTUAL-CONVENTION
	STATUS			current
	DESCRIPTION		"Indicates the severity of an alarm."
	SYNTAX			INTEGER {none(0), minor(1), major(2)}

AlarmState ::= TEXTUAL-CONVENTION
	STATUS			current
	DESCRIPTION		"Indicates state of an individual alarm."
	SYNTAX			INTEGER {clear(0), alarmed(1), informational(2), minor(3), major(4)}

FrequencyBand ::= TEXTUAL-CONVENTION
	STATUS			current
	DESCRIPTION		"Indicates the VSAT band of a unit."
	SYNTAX			INTEGER {
						standardC(3),
						instatC(4),
						extendedKu(5),
						standardKu(6),
						x(7),
						fullKu(8),
						extendedC(9),
						fullC(10),
						lowKu(11),
						palapaC(12),
						highKu(13),
						dbsBand1(14),
						dbsBand2(15),
						kaBand1(16),
						kaBand2(17),
						kuBand4(18),
						cBand6(19),
						kaBand3(20),
						kaBand4(21),
						cBandGS(22)
					}

PowerWatts ::= TEXTUAL-CONVENTION
	STATUS			current
	DESCRIPTION		"Indicates the rated power of a unit."
	SYNTAX			INTEGER {
						watt2(1),
		                watt4(2),
						watt5(3),
						watt8(4),
						watt10(5),
						watt16(6),
						watt20(7),
						watt25(8),
						watt40(9),
						watt60(10),
						watt30(11),
						watt80(12),
						watt100(13),
						watt12(14),
						watt50(15),
						watt125(16),
						watt150(17),
						watt200(18),
						watt175(19),
						watt400(20),
						watt15(21),
						watt300(22),
						watt45(23),
						watt225(24),
						watt500(25),
						watt350(26)
					}

TxMute ::= TEXTUAL-CONVENTION
	STATUS			current
	DESCRIPTION		"Indicates enable state of the PA."
	SYNTAX			INTEGER {txOff(0), txOn(1), txMutedAlarms(2), txMutedExternal(3), txMutedPowerupDelay(4)}

PositionAB ::= TEXTUAL-CONVENTION
	STATUS			current
	DESCRIPTION		"Indicates A or B positon in a redundant pair."
	SYNTAX			INTEGER {a(0), b(1)}

RedundSwitchType ::= TEXTUAL-CONVENTION
	STATUS			current
	DESCRIPTION		"Indicates the type of switching employed in a redunant
	                 pair."
	SYNTAX			INTEGER {manual(0), automatic(1)}

DisableEnableValue ::= TEXTUAL-CONVENTION
	STATUS			current
	DESCRIPTION		"Disable/Enable state."
	SYNTAX			INTEGER {disable(0), enable(1)}

RedundancyMode ::= TEXTUAL-CONVENTION
	STATUS			current
	DESCRIPTION		"Disable/Enable state."
	SYNTAX			INTEGER {reverting(0), nonreverting(1)}

RedundancyEnable ::= TEXTUAL-CONVENTION
	STATUS			current
	DESCRIPTION		"Whether or not the unit is in redundant operation."
	SYNTAX			INTEGER {notredundant(0), redundant(1)}

GainMode ::= TEXTUAL-CONVENTION
	STATUS			current
	DESCRIPTION		"Identifies the specific gain mode."
	SYNTAX			INTEGER {open(0), alc(1), agc(2)}

PowerMonitorMode ::= TEXTUAL-CONVENTION
	STATUS			current
	DESCRIPTION		"Defines the type of power data collection."
	SYNTAX			INTEGER {continuous(0), burst(1)}

MsgResponseMode ::= TEXTUAL-CONVENTION
	STATUS			current
	DESCRIPTION		"Define the level of information in response packets."
	SYNTAX			INTEGER {terse(0), verbose(1)}

ProtocolMode ::= TEXTUAL-CONVENTION
	STATUS			current
	DESCRIPTION		"Define the protocol on the FSK/485 links."
	SYNTAX			INTEGER {ascii(0), legacy(1)}

TenMHzMode ::= TEXTUAL-CONVENTION
	STATUS			current
	DESCRIPTION		"Internal or External."
	SYNTAX			INTEGER {internal(0), external(1)}
	
ArmRedundancyMode ::= TEXTUAL-CONVENTION
	STATUS			current
	DESCRIPTION		"Disable/Enable state."
	SYNTAX			INTEGER {reverting(0), nonreverting(1), warmstandby(2)}
	
END
