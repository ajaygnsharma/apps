TERRASAT-RX1PLUS1-MIB DEFINITIONS ::= BEGIN

IMPORTS
	terrasat
		FROM TERRASAT-SMI-MIB
	OBJECT-GROUP, NOTIFICATION-GROUP, MODULE-COMPLIANCE
		FROM SNMPv2-CONF
	NoYesValue, AlarmLevel, MsgResponseMode,
	DisableEnableValue,	AlarmState, RedundancyMode,
	PositionAB, RedundSwitchType
		FROM TERRASAT-TC-MIB
	IpAddress, OBJECT-TYPE, MODULE-IDENTITY, Integer32, NOTIFICATION-TYPE
		FROM SNMPv2-SMI
	sysName
		FROM RFC1213-MIB
	DisplayString
        FROM SNMPv2-TC;

rx1plus1MIB MODULE-IDENTITY
    LAST-UPDATED    "201812200000Z"
    ORGANIZATION    "Terrasat Communications, Inc."
    CONTACT-INFO
            "Terrasat Communications
            Customer Service

            Address: 235 Vineyard Court
            Morgan Hill, CA  95037
            USA

            Tel: +1 408 782-2166

            E-mail: techsupport@terrasatinc.com"
    DESCRIPTION
        "The management MIB for RX1+1 products."
	REVISION	"201812200000Z"
	DESCRIPTION
		"Added variables for RX1+1 with serial numbers
		beginning with TE82."	
	REVISION	"201410280000Z"
	DESCRIPTION
		"Added -0009 current thresholds to descriptions."
	REVISION	"201306240000Z"
	DESCRIPTION
		"Added full descriptions to alarms."
	REVISION	"201006210000Z"
	DESCRIPTION
		"Added rx1plus110MHzAlarm"
	REVISION	"200909280000Z"
	DESCRIPTION
		"The intial version."
    ::= { terrasat 2 }

rx1plus1Cfg			OBJECT IDENTIFIER ::= { rx1plus1MIB 1 }
rx1plus1IP			OBJECT IDENTIFIER ::= { rx1plus1Cfg 1 }
rx1plus1RS485		OBJECT IDENTIFIER ::= { rx1plus1Cfg 2 }
rx1plus1Alarm		OBJECT IDENTIFIER ::= { rx1plus1Cfg 3 }
rx1plus1System		OBJECT IDENTIFIER ::= { rx1plus1Cfg 4 }
rx1plus1Rx			OBJECT IDENTIFIER ::= { rx1plus1Cfg 5 }
rx1plus1Redund		OBJECT IDENTIFIER ::= { rx1plus1Cfg 6 }
rx1plus1Control		OBJECT IDENTIFIER ::= { rx1plus1MIB 2 }
rx1plus1Status		OBJECT IDENTIFIER ::= { rx1plus1MIB 3 }
rx1plus1UnitInfo	OBJECT IDENTIFIER ::= { rx1plus1Status 1 }
rx1plus1Alarms		OBJECT IDENTIFIER ::= { rx1plus1Status 2 }
rx1plus1Detector	OBJECT IDENTIFIER ::= { rx1plus1Status 3 }
rx1plus1AlarmLog	OBJECT IDENTIFIER ::= { rx1plus1Status 4 }
rx1plus1StatLog		OBJECT IDENTIFIER ::= { rx1plus1Status 5 }
rx1plus1Conformance	OBJECT IDENTIFIER ::= { rx1plus1MIB 4 }
rx1plus1Compliances	OBJECT IDENTIFIER ::= { rx1plus1Conformance 1 }
rx1plus1Groups		OBJECT IDENTIFIER ::= { rx1plus1Conformance 2 }
rx1plus1Events		OBJECT IDENTIFIER ::= { rx1plus1MIB 5 }

--
-- The Config Group
--

--
-- ip Subtree
--

rx1plus1IPAddress	OBJECT-TYPE
	SYNTAX IpAddress
	MAX-ACCESS read-write
	STATUS current
	DESCRIPTION
	"This is the network IP address for this rx1plus1. Legal values are
	1.0.0.0 to 224.0.0.0 excluding the endpoints. xx.xx.xx.00
	and xx.xx.xx.255 are excluded also. This item requires an rx1plus1
	F/W reboot to take affect."
	::= { rx1plus1IP 1 }

rx1plus1IPGateway OBJECT-TYPE
	SYNTAX IpAddress
	MAX-ACCESS read-write
	STATUS current
	DESCRIPTION
	"This is the network IP gateway address for this rx1plus1. Legal 
	values are 1.0.0.0 to 224.0.0.0 excluding the endpoints.
	xx.xx.xx.00 and xx.xx.xx.255 are excluded also. This item 
	requires an rx1plus1 F/W reboot to take affect."
	::= { rx1plus1IP 2 }

rx1plus1IPSubnet OBJECT-TYPE
	SYNTAX Integer32 (8..30)
	MAX-ACCESS read-write
	STATUS current
	DESCRIPTION
	"This is the network IP subnet mask for this RX1+1. Values range
	from 8 to 30. This is the number of 1 bits in the mask with 8 
	representing 255.0.0.0 and 30 representing 255.255.255.252.This 
	item requires an RX1+1 F/W reboot to take affect."
	::= { rx1plus1IP 3 }

rx1plus1IPTelnetPort OBJECT-TYPE
	SYNTAX Integer32 (1..65534)
	MAX-ACCESS read-write
	STATUS current
	DESCRIPTION
	"This is the telnet port for this rx1plus1. Values can range from
	1 to 65534. This item requires an rx1plus1 F/W reboot to take
	effect."
	::= { rx1plus1IP 4 }

--
-- rs485 Subtree
--

rx1plus1RS485Address OBJECT-TYPE
	SYNTAX Integer32 (1..254)
	MAX-ACCESS read-write
	STATUS current
	DESCRIPTION
	"This is 485 network address for this rx1plus1. Legal values are 
	1 to 254."
	::= { rx1plus1RS485 1 }

rx1plus1RS485Baudrate OBJECT-TYPE
	SYNTAX Integer32 (1200|2400|4800|9600|19200|38400|56700|115200)
	MAX-ACCESS read-write
	STATUS current
	DESCRIPTION
	"This is the 485 baudrate of this rx1plus1.
	1200, 2400, 4800, 9600, 19200, 38400, 57600, 115200"
	::= { rx1plus1RS485 2 }

rx1plus1RS485Delay OBJECT-TYPE
	SYNTAX Integer32 (1..255)
	MAX-ACCESS read-write
	STATUS current
	DESCRIPTION
	"This is the RS485 line delay for this rx1plus1. Legal Values are
	1 to 255."
	::= { rx1plus1RS485 3 }

rx1plus1RS485Mode OBJECT-TYPE
        SYNTAX  INTEGER {ascii(0),binary(1)}
        MAX-ACCESS      read-write
        STATUS  current
        DESCRIPTION
        "This is the RS485 protocol mode. Legal Values are
        (0) enable ASCII protocol
        (1) enable Terrasat binary mode."
        ::= { rx1plus1RS485 4 }
	
--
-- alarm Subtree
--

rx1plus1InputLowThresholdSuppressibleA OBJECT-TYPE
	SYNTAX NoYesValue
	MAX-ACCESS read-write
	STATUS current
	DESCRIPTION
	"The value of this object configures A Input Low Threshold
	alarm suppression.
	(0) disallow suppression
	(1) allow suppression"
	::= { rx1plus1Alarm 1 }

rx1plus1InputLowThresholdSuppressibleB OBJECT-TYPE
	SYNTAX NoYesValue
	MAX-ACCESS read-write
	STATUS current
	DESCRIPTION
	"The value of this object configures B Input Low Threshold
	alarm suppression.
	(0) disallow suppression
	(1) allow suppression"
	::= { rx1plus1Alarm 2 }

rx1plus1VDCLowThresholdSuppressibleA OBJECT-TYPE
	SYNTAX NoYesValue
	MAX-ACCESS read-write
	STATUS current
	DESCRIPTION
	"The value of this object configures A VDC Low Threshold
	alarm suppression.
	(0) disallow suppression
	(1) allow suppression"
	::= { rx1plus1Alarm 3 }

rx1plus1VDCLowThresholdSuppressibleB OBJECT-TYPE
	SYNTAX NoYesValue
	MAX-ACCESS read-write
	STATUS current
	DESCRIPTION
	"The value of this object configures B VDC Low Threshold
	alarm suppression.
	(0) disallow suppression
	(1) allow suppression"
	::= { rx1plus1Alarm 4 }

rx1plus1VDCHighThresholdSuppressibleA OBJECT-TYPE
	SYNTAX NoYesValue
	MAX-ACCESS read-write
	STATUS current
	DESCRIPTION
	"The value of this object configures A VDC High Threshold
	alarm suppression.
	(0) disallow suppression
	(1) allow suppression"
	::= { rx1plus1Alarm 5 }

rx1plus1VDCHighThresholdSuppressibleB OBJECT-TYPE
	SYNTAX NoYesValue
	MAX-ACCESS read-write
	STATUS current
	DESCRIPTION
	"The value of this object configures B VDC High Threshold
	alarm suppression.
	(0) disallow suppression
	(1) allow suppression"
	::= { rx1plus1Alarm 6 }

rx1plus1IDCLowThresholdSuppressibleA OBJECT-TYPE
	SYNTAX NoYesValue
	MAX-ACCESS read-write
	STATUS current
	DESCRIPTION
	"The value of this object configures A IDC Low Threshold
	alarm suppression.
	(0) disallow suppression
	(1) allow suppression"
	::= { rx1plus1Alarm 7 }

rx1plus1IDCLowThresholdSuppressibleB OBJECT-TYPE
	SYNTAX NoYesValue
	MAX-ACCESS read-write
	STATUS current
	DESCRIPTION
	"The value of this object configures B IDC Low Threshold
	alarm suppression.
	(0) disallow suppression
	(1) allow suppression"
	::= { rx1plus1Alarm 8 }

rx1plus1IDCHighThresholdSuppressibleA OBJECT-TYPE
	SYNTAX NoYesValue
	MAX-ACCESS read-write
	STATUS current
	DESCRIPTION
	"The value of this object configures A IDC High Threshold
	alarm suppression.
	(0) disallow suppression
	(1) allow suppression"
	::= { rx1plus1Alarm 9 }

rx1plus1IDCHighThresholdSuppressibleB OBJECT-TYPE
	SYNTAX NoYesValue
	MAX-ACCESS read-write
	STATUS current
	DESCRIPTION
	"The value of this object configures B IDC High Threshold
	alarm suppression.
	(0) disallow suppression
	(1) allow suppression"
	::= { rx1plus1Alarm 10 }

rx1plus1InputLowThresholdAlarmLevelA OBJECT-TYPE
	SYNTAX AlarmLevel
	MAX-ACCESS read-write
	STATUS current
	DESCRIPTION
	"The value of this object configures whether the A Input Low Threshold 
	alarm generates no alarm, a minor alarm, or a major alarm.
	(0) no alarm
	(1) minor alarm
	(2) major alarm"             
	::= { rx1plus1Alarm 11 }

rx1plus1InputLowThresholdAlarmLevelB OBJECT-TYPE
	SYNTAX AlarmLevel
	MAX-ACCESS read-write
	STATUS current
	DESCRIPTION
	"The value of this object configures whether the B Input Low Threshold 
	alarm generates no alarm, a minor alarm, or a major alarm.
	(0) no alarm
	(1) minor alarm
	(2) major alarm"             
	::= { rx1plus1Alarm 12 }

rx1plus1VDCLowThresholdAlarmLevelA OBJECT-TYPE
	SYNTAX AlarmLevel
	MAX-ACCESS read-write
	STATUS current
	DESCRIPTION
	"The value of this object configures whether the A VDC Low Threshold 
	alarm generates no alarm, a minor alarm, or a major alarm.
	(0) no alarm
	(1) minor alarm
	(2) major alarm"             
	::= { rx1plus1Alarm 13 }

rx1plus1VDCLowThresholdAlarmLevelB OBJECT-TYPE
	SYNTAX AlarmLevel
	MAX-ACCESS read-write
	STATUS current
	DESCRIPTION
	"The value of this object configures whether the B VDC Low Threshold 
	alarm generates no alarm, a minor alarm, or a major alarm.
	(0) no alarm
	(1) minor alarm
	(2) major alarm"             
	::= { rx1plus1Alarm 14 }

rx1plus1VDCHighThresholdAlarmLevelA OBJECT-TYPE
	SYNTAX AlarmLevel
	MAX-ACCESS read-write
	STATUS current
	DESCRIPTION
	"The value of this object configures whether the A VDC High Threshold 
	alarm generates no alarm, a minor alarm, or a major alarm.
	(0) no alarm
	(1) minor alarm
	(2) major alarm"             
	::= { rx1plus1Alarm 15 }

rx1plus1VDCHighThresholdAlarmLevelB OBJECT-TYPE
	SYNTAX AlarmLevel
	MAX-ACCESS read-write
	STATUS current
	DESCRIPTION
	"The value of this object configures whether the B VDC High Threshold 
	alarm generates no alarm, a minor alarm, or a major alarm.
	(0) no alarm
	(1) minor alarm
	(2) major alarm"             
	::= { rx1plus1Alarm 16 }

rx1plus1IDCLowThresholdAlarmLevelA OBJECT-TYPE
	SYNTAX AlarmLevel
	MAX-ACCESS read-write
	STATUS current
	DESCRIPTION
	"The value of this object configures whether the A IDC Low Threshold 
	alarm generates no alarm, a minor alarm, or a major alarm.
	(0) no alarm
	(1) minor alarm
	(2) major alarm"             
	::= { rx1plus1Alarm 17 }

rx1plus1IDCLowThresholdAlarmLevelB OBJECT-TYPE
	SYNTAX AlarmLevel
	MAX-ACCESS read-write
	STATUS current
	DESCRIPTION
	"The value of this object configures whether the B IDC Low Threshold 
	alarm generates no alarm, a minor alarm, or a major alarm.
	(0) no alarm
	(1) minor alarm
	(2) major alarm"             
	::= { rx1plus1Alarm 18 }

rx1plus1IDCHighThresholdAlarmLevelA OBJECT-TYPE
	SYNTAX AlarmLevel
	MAX-ACCESS read-write
	STATUS current
	DESCRIPTION
	"The value of this object configures whether the A IDC High Threshold 
	alarm generates no alarm, a minor alarm, or a major alarm.
	(0) no alarm
	(1) minor alarm
	(2) major alarm"             
	::= { rx1plus1Alarm 19 }

rx1plus1IDCHighThresholdAlarmLevelB OBJECT-TYPE
	SYNTAX AlarmLevel
	MAX-ACCESS read-write
	STATUS current
	DESCRIPTION
	"The value of this object configures whether the B IDC high Threshold 
	alarm generates no alarm, a minor alarm, or a major alarm.
	(0) no alarm
	(1) minor alarm
	(2) major alarm"             
	::= { rx1plus1Alarm 20 }

rx1plus110MHzAlarm OBJECT-TYPE
	SYNTAX DisableEnableValue
	MAX-ACCESS read-write
	STATUS current
	DESCRIPTION
	"The value of this object configures whether the 10MHz alarm is generated.
	(0) disable
	(1) enable"             
	::= { rx1plus1Alarm 21 }

--
-- system Subtree
--

rx1plus1VerboseMode OBJECT-TYPE
	SYNTAX MsgResponseMode
	MAX-ACCESS read-write
	STATUS current
	DESCRIPTION
	"The value of this object sets the response type for messages
	received utilizing the telnet command set.
	(0) Terse messages
	(1) Verbose messages"
	::= { rx1plus1System 1 }

rx1plus1Echo OBJECT-TYPE
	SYNTAX DisableEnableValue
	MAX-ACCESS read-write
	STATUS current
	DESCRIPTION
	"The value of this object sets the echo type for messages
	received utilizing the telnet command set.
	(0) No Echo
	(1) Echo"
	::= { rx1plus1System 2 }

rx1plus1PasswordTimeOut OBJECT-TYPE
	SYNTAX Integer32 (1..65535)
	MAX-ACCESS read-write
	STATUS current
	DESCRIPTION
	"The value of this object sets the password timeout for all
	interfaces excluding snmp.
	(0) no password timeout
	(1..65535) number of minutes"
	::= { rx1plus1System 3 }

rx1plus1WebServerRefresh OBJECT-TYPE
	SYNTAX Integer32 (1..65535)
	MAX-ACCESS read-write
	STATUS current
	DESCRIPTION
	"The value of this object sets the web server refresh rate
	(0) no refresh
	(1..3600) number of seconds"
	::= { rx1plus1System 4 }

rx1plus1RealTimeClock OBJECT-TYPE
	SYNTAX  DisplayString (SIZE (19))
	MAX-ACCESS      read-write
	STATUS  current
	DESCRIPTION
	"This is the real time clock.
	Format is MM/dd/yyyy hh:mm:ss.
	Time is based on 24 hour clock."
	::= { rx1plus1System 5 }
        
rx1plus1NtpIpAddr OBJECT-TYPE
	SYNTAX  IpAddress
	MAX-ACCESS      read-write
	STATUS  current
	DESCRIPTION
	"This is the NTP server IP address. Legal values are
	1.0.0.0 to 224.0.0.0 excluding the endpoints, network, loopback,
	and broadcast addresses."
	::= { rx1plus1System 6 }

rx1plus1TimezoneOffset OBJECT-TYPE
	SYNTAX  Integer32 (-720..840)
	UNITS	"Minutes"
	MAX-ACCESS      read-write
	STATUS  current
	DESCRIPTION
	"This is the offset for GMT served by NTP. It may range from
	GMT+14(840) to GMT-12(-720). Format is in minutes.
	No offset is 0."
	::= { rx1plus1System 7 }
	
rx1plus1WebPageTitle OBJECT-TYPE
	SYNTAX  DisplayString (SIZE (0..32))
	MAX-ACCESS      read-write
	STATUS  current
	DESCRIPTION
	"This is the user configurable title displayed at the top
	of web pages."
	::= { rx1plus1System 8 }
	
--
-- rx Subtree
--

rx1plus1InputThresholdLowA OBJECT-TYPE
	SYNTAX Integer32 (1..65535)
	MAX-ACCESS read-write
	STATUS current
	DESCRIPTION
	"The value of this object uniquely identifies the
	Input Low Threshold setting in mB for this rx1plus1.
	Range is -4000 to 500."
	::= { rx1plus1Rx 1 }

rx1plus1InputThresholdLowB OBJECT-TYPE
	SYNTAX Integer32 (1..65535)
	MAX-ACCESS read-write
	STATUS current
	DESCRIPTION
	"The value of this object uniquely identifies the
	Input Low Threshold setting in mB for this rx1plus1. 
	Range is -4000 to 500."
	::= { rx1plus1Rx 2 }

rx1plus1VDCHighThresholdA OBJECT-TYPE
	SYNTAX Integer32 (1..65535)
	MAX-ACCESS read-write
	STATUS current
	DESCRIPTION
	"The value of this object uniquely identifies the
	Input High Threshold setting in mVolts for this rx1plus1. 
	Range is 1000 to 2500
	Must be greater than cfgVDCLowThresholdA."
	::= { rx1plus1Rx 3 }

rx1plus1VDCHighThresholdB OBJECT-TYPE
	SYNTAX Integer32 (1..65535)
	MAX-ACCESS read-write
	STATUS current
	DESCRIPTION
	"The value of this object uniquely identifies the
	Input High Threshold setting in mVolts for this rx1plus1. 
	Range is 1000 to 2500
	Must be greater than cfgVDCLowThresholdB."
	::= { rx1plus1Rx 4 }

rx1plus1VDCLowThresholdA OBJECT-TYPE
	SYNTAX Integer32 (1..65535)
	MAX-ACCESS read-write
	STATUS current
	DESCRIPTION
	"The value of this object uniquely identifies the
	Input Low Threshold setting in mVolts for this rx1plus1. 
	Range is 1000 to 2500
	Must be less than cfgVDCHighThresholdA."
	::= { rx1plus1Rx 5 }

rx1plus1VDCLowThresholdB OBJECT-TYPE
	SYNTAX Integer32 (1..65535)
	MAX-ACCESS read-write
	STATUS current
	DESCRIPTION
	"The value of this object uniquely identifies the
	Input Low Threshold setting in mVolts for this rx1plus1. 
	Range is 1000 to 2500
	Must be less than cfgVDCHighThresholdB."
	::= { rx1plus1Rx 6 }

rx1plus1IDCHighThresholdA OBJECT-TYPE
	SYNTAX Integer32 (1..65535)
	MAX-ACCESS read-write
	STATUS current
	DESCRIPTION
	"The value of this object uniquely identifies the
	Input High Threshold setting in mAmps for this rx1plus1. 
	Range is 100 to 600
	Model 310-10801-0009 Range is 100 to 1200
	Must be greater than cfgIDCLowThresholdA."
	::= { rx1plus1Rx 7 }

rx1plus1IDCHighThresholdB OBJECT-TYPE
	SYNTAX Integer32 (1..65535)
	MAX-ACCESS read-write
	STATUS current
	DESCRIPTION
	"The value of this object uniquely identifies the
	Input High Threshold setting in mAmps for this rx1plus1. 
	Range is 100 to 600
	Model 310-10801-0009 Range is 100 to 1200
	Must be greater than cfgIDCLowThresholdB."
	::= { rx1plus1Rx 8 }

rx1plus1IDCLowThresholdA OBJECT-TYPE
	SYNTAX Integer32 (1..65535)
	MAX-ACCESS read-write
	STATUS current
	DESCRIPTION
	"The value of this object uniquely identifies the
	Input Low Threshold setting in mAmps for this rx1plus1. 
	Range is 100 to 600
	Model 310-10801-0009 Range is 100 to 1200
	Must be less than cfgIDCHighThresholdA."
	::= { rx1plus1Rx 9 }

rx1plus1IDCLowThresholdB OBJECT-TYPE
	SYNTAX Integer32 (1..65535)
	MAX-ACCESS read-write
	STATUS current
	DESCRIPTION
	"The value of this object uniquely identifies the
	Input Low Threshold setting in mAmps for this rx1plus1. 
	Range is 100 to 600
	Model 310-10801-0009 Range is 100 to 1200
	Must be less than cfgIDCHighThresholdB."
	::= { rx1plus1Rx 10 }

rx1plus1BandVolts OBJECT-TYPE
	SYNTAX INTEGER	{ volt24(0),volt18(1),volt15(2),volt13(3) }
	MAX-ACCESS read-write
	STATUS current
	DESCRIPTION
	"This changes LNB supply voltage for selecting bands."
	::= { rx1plus1Rx 11 }

rx1plus1Band22khz OBJECT-TYPE
	SYNTAX INTEGER	{off(0), on(1)}
	MAX-ACCESS read-write
	STATUS current
	DESCRIPTION
	"This enables 22KHz to LNB for selecting bands."
	::= { rx1plus1Rx 12 }

rx1plus1Trim10mhz1 OBJECT-TYPE
	SYNTAX Integer32 (0..4095)
	MAX-ACCESS read-write
	STATUS current
	DESCRIPTION
	"This adjusts the frequency of the first internal
	10MHz card."
	::= { rx1plus1Rx 13 }

rx1plus1Trim10mhz2 OBJECT-TYPE
	SYNTAX Integer32 (0..4095)
	MAX-ACCESS read-write
	STATUS current
	DESCRIPTION
	"This adjusts the frequency of the second internal
	10MHz card."
	::= { rx1plus1Rx 14 }

rx1plus1TenMHzEnable OBJECT-TYPE
	SYNTAX INTEGER	{auto(0), int1(1), int2(2)}
	MAX-ACCESS read-write
	STATUS current
	DESCRIPTION
	"This allows the user to select either of the internal
	10MHz sources for maintenance. This is only available
	on units that have 2 internal 10MHz sources.
	0 - Automatic selection of source (Default).
	1 - Select internal 10MHz #1
	2 - Select internal 10MHz #2"
	::= { rx1plus1Rx 15 }
	
-- 
-- redund Subtree
--

rx1plus1RedundancyMode OBJECT-TYPE
	SYNTAX RedundancyMode
	MAX-ACCESS read-write
	STATUS current
	DESCRIPTION
	"The value of this object uniquely identifies the
	redundancy switching mode of rx1plus1.
	(0) Reverting
	(1) NonReverting"
	::= { rx1plus1Redund 1 }

rx1plus1SwitchingType OBJECT-TYPE
	SYNTAX RedundSwitchType
	MAX-ACCESS read-write
	STATUS current
	DESCRIPTION
	"The value of this object uniquely identifies the
	switching type of the rx1plus1.
	(0) Manual switching
	(1) Automatic switching"
	::= { rx1plus1Redund 2 }

rx1plus1SwitchPosition OBJECT-TYPE
	SYNTAX PositionAB
	MAX-ACCESS read-write
	STATUS current
	DESCRIPTION
	"The value of this object uniquely identifies the
	switch positon of the rx1plus1. Reading this variable
	shows the current waveguide switch position. Writing
	this variable changes the current switch position.
	(0) Switch position A
	(1) Switch position B"
	::= { rx1plus1Redund 3 }

rx1plus1SystemStatus OBJECT-TYPE
	SYNTAX OCTET STRING (SIZE (0..100))
	MAX-ACCESS read-only
	STATUS current
	DESCRIPTION
	"The value of this object uniquely identifies the
	redundant system status of the rx1plus1."
	::= { rx1plus1Redund 4 }

--
-- The Control Group
--

rx1plus1SuppressAlarmsA OBJECT-TYPE
	SYNTAX NoYesValue
	MAX-ACCESS read-write
	STATUS current
	DESCRIPTION
	"The value of this object causes configured threshold
	alarms to be suppressed.
	(0) No Suppression
	(1) Suppress configured threshold alarms"
	::= { rx1plus1Control 1 }

rx1plus1SuppressAlarmsB OBJECT-TYPE
	SYNTAX NoYesValue
	MAX-ACCESS read-write
	STATUS current
	DESCRIPTION
	"The value of this object causes configured threshold
	alarms to be suppressed.
	(0) No Suppression
	(1) Suppress configured threshold alarms"
	::= { rx1plus1Control 2 }

rx1plus1SimulateAlarmA OBJECT-TYPE
	SYNTAX NoYesValue
	MAX-ACCESS read-write
	STATUS current
	DESCRIPTION
	"The value of this object causes an A side major alarm
	in the rx1plus1.
	(0) No Alarm
	(1) Simulate a Tx alarm"
	::= { rx1plus1Control 3 }

rx1plus1SimulateAlarmB OBJECT-TYPE
	SYNTAX NoYesValue
	MAX-ACCESS read-write
	STATUS current
	DESCRIPTION
	"The value of this object causes a B side major alarm
	in the rx1plus1.
	(0) No Alarm
	(1) Simulate a Tx alarm"
	::= { rx1plus1Control 4 }

rx1plus1ClearAlarmLog OBJECT-TYPE
	SYNTAX Integer32 (0)
	MAX-ACCESS read-write
	STATUS current
	DESCRIPTION
	"The value of this object causes the rx1plus1 to clear
	its alarm history.
	(0) Clear alarm history"
	::= { rx1plus1Control 5 }

rx1plus1FirmwareReboot OBJECT-TYPE
	SYNTAX Integer32 (0)
	MAX-ACCESS read-write
	STATUS current
	DESCRIPTION
	"The value of this object causes the firmware to
	restart. Writing this object will cause a momentary
	interruption to traffic.
	(0) Reboot Firmware"
	::= { rx1plus1Control 6 }

--
-- The Status Group
--


--
-- unitInfo Subtree
--

rx1plus1ModelNumber OBJECT-TYPE
	SYNTAX OCTET STRING (SIZE (0..20))
	MAX-ACCESS read-only
	STATUS current
	DESCRIPTION
	"The value of this object identifies the
	model number of this rx1plus1."
	::= { rx1plus1UnitInfo 1 }

rx1plus1SerialNumber OBJECT-TYPE
	SYNTAX OCTET STRING (SIZE (0..20))
	MAX-ACCESS read-only
	STATUS current
	DESCRIPTION
	"The value of this object identifies the
	serial number of this rx1plus1."
	::= { rx1plus1UnitInfo 2 }

rx1plus1FirmwareVersion OBJECT-TYPE
	SYNTAX OCTET STRING (SIZE (0..50))
	MAX-ACCESS read-only
	STATUS current
	DESCRIPTION
	"The value of this object identifies the
	Firmware Version of this rx1plus1."
	::= { rx1plus1UnitInfo 3 }

rx1plus1HardwareVersion OBJECT-TYPE
	SYNTAX DisplayString
	MAX-ACCESS read-only
	STATUS current
	DESCRIPTION
	"The value of this object identifies the
	Firmware Version of this rx."
	::= { rx1plus1UnitInfo 4 }

rx1plus1SupplyVoltRange OBJECT-TYPE
	SYNTAX DisplayString
	MAX-ACCESS read-only
	STATUS current
	DESCRIPTION
	"AC or DC input voltage range."
	::= { rx1plus1UnitInfo 5 }
	
rx1plus1Provider OBJECT-TYPE
	SYNTAX DisplayString
	MAX-ACCESS read-only
	STATUS current
	DESCRIPTION
	"This is the support entity to contact."
	::= { rx1plus1UnitInfo 6 }

--
-- alarms Subtree
--

rx1plus1InputThresholdALow OBJECT-TYPE
	SYNTAX AlarmState
	MAX-ACCESS read-only
	STATUS current
	DESCRIPTION
	"The value of object identifies whether a 
	Input Threshold Low alarm exists.
	(0) No Alarm
	(1) Alarm
	(2) Informational
	(3) Minor
	(4) Major
	"
	::= { rx1plus1Alarms 1 }

rx1plus1InputThresholdBLow OBJECT-TYPE
	SYNTAX AlarmState
	MAX-ACCESS read-only
	STATUS current
	DESCRIPTION
	"The value of object identifies whether a 
	Input Threshold Low alarm exists.
	(0) No Alarm
	(1) Alarm
	(2) Informational
	(3) Minor
	(4) Major
	"
	::= { rx1plus1Alarms 2 }

rx1plus110MHz OBJECT-TYPE
	SYNTAX AlarmState
	MAX-ACCESS read-only
	STATUS current
	DESCRIPTION
	"The value of object identifies whether a 
	10 MHz alarm exists.
	(0) No Alarm
	(1) Alarm
	(2) Informational
	(3) Minor
	(4) Major
	"
	::= { rx1plus1Alarms 3 }

rx1plus1RxSimulatedA OBJECT-TYPE
	SYNTAX AlarmState
	MAX-ACCESS read-only
	STATUS current
	DESCRIPTION
	"The value of object identifies whether an 
	A Rx Simulated alarm exists.
	(0) No Alarm
	(1) Alarm
	(2) Informational
	(3) Minor
	(4) Major
	"
	::= { rx1plus1Alarms 4 }

rx1plus1RxSimulatedB OBJECT-TYPE
	SYNTAX AlarmState
	MAX-ACCESS read-only
	STATUS current
	DESCRIPTION
	"The value of object identifies whether an 
	B Rx Simulated alarm exists.
	(0) No Alarm
	(1) Alarm
	(2) Informational
	(3) Minor
	(4) Major
	"
	::= { rx1plus1Alarms 5 }

rx1plus1VdcLowAThreshold OBJECT-TYPE
	SYNTAX AlarmState
	MAX-ACCESS read-only
	STATUS current
	DESCRIPTION
	"The value of object identifies whether an
	A voltage out of range low alarm exists.
	(0) No Alarm
	(1) Alarm
	(2) Informational
	(3) Minor
	(4) Major
	"
	::= { rx1plus1Alarms 6 }

rx1plus1VdcLowBThreshold OBJECT-TYPE
	SYNTAX AlarmState
	MAX-ACCESS read-only
	STATUS current
	DESCRIPTION
	"The value of object identifies whether a
	B voltage out of range low alarm exists.
	(0) No Alarm
	(1) Alarm
	(2) Informational
	(3) Minor
	(4) Major
	"
	::= { rx1plus1Alarms 7 }

rx1plus1VdcHighAThreshold OBJECT-TYPE
	SYNTAX AlarmState
	MAX-ACCESS read-only
	STATUS current
	DESCRIPTION
	"The value of object identifies whether an
	A voltage out of range high alarm exists.
	(0) No Alarm
	(1) Alarm
	(2) Informational
	(3) Minor
	(4) Major
	"
	::= { rx1plus1Alarms 8 }

rx1plus1VdcHighBThreshold OBJECT-TYPE
	SYNTAX AlarmState
	MAX-ACCESS read-only
	STATUS current
	DESCRIPTION
	"The value of object identifies whether a
	B voltage out of range high alarm exists.
	(0) No Alarm
	(1) Alarm
	(2) Informational
	(3) Minor
	(4) Major
	"
	::= { rx1plus1Alarms 9 }

rx1plus1IdcLowAThreshold OBJECT-TYPE
	SYNTAX AlarmState
	MAX-ACCESS read-only
	STATUS current
	DESCRIPTION
	"The value of object identifies whether an 
	A Current out of range low alarm exists.
	(0) No Alarm
	(1) Alarm
	(2) Informational
	(3) Minor
	(4) Major
	"
	::= { rx1plus1Alarms 10 }

rx1plus1IdcLowBThreshold OBJECT-TYPE
	SYNTAX AlarmState
	MAX-ACCESS read-only
	STATUS current
	DESCRIPTION
	"The value of object identifies whether a 
	B Current out of range low alarm exists.
	(0) No Alarm
	(1) Alarm
	(2) Informational
	(3) Minor
	(4) Major
	"
	::= { rx1plus1Alarms 11 }

rx1plus1IdcHighAThreshold OBJECT-TYPE
	SYNTAX AlarmState
	MAX-ACCESS read-only
	STATUS current
	DESCRIPTION
	"The value of object identifies whether an 
	A Current out of range high alarm exists.
	(0) No Alarm
	(1) Alarm
	(2) Informational
	(3) Minor
	(4) Major
	"
	::= { rx1plus1Alarms 12 }

rx1plus1IdcHighBThreshold OBJECT-TYPE
	SYNTAX AlarmState
	MAX-ACCESS read-only
	STATUS current
	DESCRIPTION
	"The value of object identifies whether a 
	B Current out of range high alarm exists.
	(0) No Alarm
	(1) Alarm
	(2) Informational
	(3) Minor
	(4) Major
	"
	::= { rx1plus1Alarms 13 }

rx1plus1EmergencyOverride OBJECT-TYPE
	SYNTAX AlarmState
	MAX-ACCESS read-only
	STATUS current
	DESCRIPTION
	"The value of object identifies whether the 
	emergency override switch is active.
	(0) No Alarm
	(1) Alarm
	(2) Informational
	(3) Minor
	(4) Major
	"
	::= { rx1plus1Alarms 14 }

rx1plus1SwitchFault OBJECT-TYPE
	SYNTAX AlarmState
	MAX-ACCESS read-only
	STATUS current
	DESCRIPTION
	"The value of object identifies whether a 
	waveguide switch alarm exists.
	(0) No Alarm
	(1) Alarm
	(2) Informational
	(3) Minor
	(4) Major
	"
	::= { rx1plus1Alarms 15 }

rx1plus1LogAlignError OBJECT-TYPE
	SYNTAX AlarmState
	MAX-ACCESS read-only
	STATUS current
	DESCRIPTION
	"The value of object identifies whether a 
	alarm log alignment error alarm exists.
	This indicates a corruption in the alarm log.
	(0) No Alarm
	(1) Alarm
	(2) Informational
	(3) Minor
	(4) Major
	"
	::= { rx1plus1Alarms 16 }

rx1plus1CfgDataError OBJECT-TYPE
	SYNTAX AlarmState
	MAX-ACCESS read-only
	STATUS current
	DESCRIPTION
	"The value of object identifies whether a 
	configuration data read error alarm exists.
	This indicates an error has occurred reading
	the saved configuration data.
	(0) No Alarm
	(1) Alarm
	(2) Informational
	(3) Minor
	(4) Major
	"
	::= { rx1plus1Alarms 17 }

rx1plus1EthernetDownload OBJECT-TYPE
	SYNTAX AlarmState
	MAX-ACCESS read-only
	STATUS current
	DESCRIPTION
	"The value of object identifies whether 
	the rx1plus1 is downloading new firmware over
	the ethernet link.
	(0) No Alarm
	(1) Alarm
	(2) Informational
	(3) Minor
	(4) Major
	"
	::= { rx1plus1Alarms 18 }

rx1plus1SerialDownload OBJECT-TYPE
	SYNTAX AlarmState
	MAX-ACCESS read-only
	STATUS current
	DESCRIPTION
	"The value of object identifies whether a 
	the rx1plus1 is downloading new firmware over
	the serial link.
	(0) No Alarm
	(1) Alarm
	(2) Informational
	(3) Minor
	(4) Major
	"
	::= { rx1plus1Alarms 19 }

rx1plus1FWReboot OBJECT-TYPE
	SYNTAX AlarmState
	MAX-ACCESS read-only
	STATUS current
	DESCRIPTION
	"The value of object identifies whether 
	the rx1plus1 firmware has been rebooted.
	(0) No Alarm
	(1) Alarm
	(2) Informational
	(3) Minor
	(4) Major
	"
	::= { rx1plus1Alarms 20 }

rx1plus1Internal10MHz1 OBJECT-TYPE
	SYNTAX AlarmState
	MAX-ACCESS read-only
	STATUS current
	DESCRIPTION
	"If the RX has 2 internal 10MHz sources,
	this value will alert the user to a possible
	failure of internal 10MHz #1.
	(0) No Alarm
	(1) Alarm
	(2) Informational
	(3) Minor
	(4) Major
	"
	::= { rx1plus1Alarms 21 }

--
-- detector Subtree
--

rx1plus1DCVoltageA OBJECT-TYPE
	SYNTAX Integer32 (1..65535)
	MAX-ACCESS read-only
	STATUS current
	DESCRIPTION
	"The value of this object identifies the
	A DC voltage level of the rx1plus1. Values range
	from 100 to 250 representing 10.00 to 25.00 volts
	in .1 volt increments."
	::= { rx1plus1Detector 1 }

rx1plus1DCVoltageB OBJECT-TYPE
	SYNTAX Integer32 (1..65535)
	MAX-ACCESS read-only
	STATUS current
	DESCRIPTION
	"The value of this object identifies the
	B DC voltage level of the rx1plus1. Values range
	from 100 to 250 representing 10.00 to 25.00 volts
	in .1 volt increments."
	::= { rx1plus1Detector 2 }

rx1plus1DCCurrentA OBJECT-TYPE
	SYNTAX Integer32 (1..65535)
	MAX-ACCESS read-only
	STATUS current
	DESCRIPTION
	"The value of this object identifies the
	A DC current consumption of the rx1plus1. Values range
	from 100 miliamps to 600 milliamps."
	::= { rx1plus1Detector 3 }

rx1plus1DCCurrentB OBJECT-TYPE
	SYNTAX Integer32 (1..65535)
	MAX-ACCESS read-only
	STATUS current
	DESCRIPTION
	"The value of this object identifies the
	B DC current consumption of the rx1plus1. Values range
	from 100 miliamps to 600 milliamps."
	::= { rx1plus1Detector 4 }

rx1plus1InputPowerLevelA OBJECT-TYPE
	SYNTAX Integer32 (1..65535)
	MAX-ACCESS read-only
	STATUS current
	DESCRIPTION
	"The value of this object identifies the
	A input power level of the rx1plus1. Values range
	from -4000 to 500 representing -40.00 to 5.00 dbm."
	::= { rx1plus1Detector 5 }

rx1plus1InputPowerLevelB OBJECT-TYPE
	SYNTAX Integer32 (1..65535)
	MAX-ACCESS read-only
	STATUS current
	DESCRIPTION
	"The value of this object identifies the
	B input power level of the rx1plus1. Values range
	from -4000 to 500 representing -40.00 to 5.00 dbm."
	::= { rx1plus1Detector 6 }

rx1plus1TenMegLevel OBJECT-TYPE
	SYNTAX Integer32
	MAX-ACCESS read-only
	STATUS current
	DESCRIPTION
	"The value of this object identifies the
	current 10MHz source level. Divide by 10
	for floating point level in dBm"
	::= { rx1plus1Detector 7 }
	
--
-- alarmsLog Subtree
--

rx1plus1AlarmLogNumber OBJECT-TYPE
	SYNTAX Integer32 (0..40)
	MAX-ACCESS read-only
	STATUS current
	DESCRIPTION
	"The value of this object uniquely identifies the
	current number of alarm log entries."
	::= { rx1plus1AlarmLog 1 }

rx1plus1AlarmLogTable OBJECT-TYPE
	SYNTAX SEQUENCE OF Rx1plus1AlarmLogEntry
	MAX-ACCESS not-accessible
	STATUS current
	DESCRIPTION
	"This is a table of alarm log entries."
	::= { rx1plus1AlarmLog 2 }

rx1plus1AlarmLogEntry OBJECT-TYPE
	SYNTAX Rx1plus1AlarmLogEntry
	MAX-ACCESS not-accessible
	STATUS current
	DESCRIPTION
	"This is a table of alarm log entries."
	INDEX {rx1plus1AlarmLogIndex}
	::= { rx1plus1AlarmLogTable 1 }

Rx1plus1AlarmLogEntry ::= SEQUENCE {
	rx1plus1AlarmLogIndex	Integer32,
	rx1plus1AlarmLogType	INTEGER,
	rx1plus1AlarmLogAlarms	Integer32
}

rx1plus1AlarmLogIndex OBJECT-TYPE
	SYNTAX Integer32 (1..40)
	MAX-ACCESS not-accessible
	STATUS current
	DESCRIPTION
	"The value of this object uniquely identifies this
	alarm log entry."
	::= { rx1plus1AlarmLogEntry 1 }

rx1plus1AlarmLogType OBJECT-TYPE
	SYNTAX INTEGER {rx(0), misc(1)}
	MAX-ACCESS read-only
	STATUS current
	DESCRIPTION
	"The value of this object uniquely identifies this
	alarm log entry's alarm type
	(0) Rx Alarms
	(1) Misc Alarms."
	::= { rx1plus1AlarmLogEntry 2 }

rx1plus1AlarmLogAlarms OBJECT-TYPE
	SYNTAX Integer32 (1..65535)
	MAX-ACCESS read-only
	STATUS current
	DESCRIPTION
	"The value of this object uniquely identifies this
	alarm log entry's alarms. The values of this entry
	are based on the value of alarmsLogType above.
	If the value is Rx Alarms then the following bitmap applies:

	(0x0001) A input level low
	(0x0002) B input level low
	(0x0004) A simulated alarm
	(0x0008) B simulated alarm
	(0x0010) 10 MHz reference
	(0x0020) A VDC threshold low
	(0x0040) A VDC threshold high
	(0x0080) B VDC threshold low
	(0x0100) B VDC threshold high
	(0x0200) Waveguide switch fault
	(0x0400) A IDC threshold low
	(0x0800) A IDC threshold high
	(0x1000) B IDC threshold low
	(0x2000) B IDC threshold high
	(0x4000) Emergency override switch
	(0x8000) Value of 0 indicates this is RX alarms.

	If the value ov alarmsLogType is Misc Alarms then
	the following bitmap applies:

	(0x0001) Event log corrupted
	(0x0002) Configuration reset
	(0x0004) Ethernet download
	(0x0008) Serial download
	(0x0010) Reboot
	(0xFFE0) Not used"
	::= { rx1plus1AlarmLogEntry 3 }

rx1plus1EventLogTable OBJECT-TYPE
        SYNTAX  SEQUENCE OF Rx1plus1EventLogEntry
        MAX-ACCESS      not-accessible
        STATUS  current
        DESCRIPTION
        "This is a table of alarm log entries."
        ::= { rx1plus1AlarmLog 3 }

rx1plus1EventLogEntry OBJECT-TYPE
        SYNTAX  Rx1plus1EventLogEntry
        MAX-ACCESS      not-accessible
        STATUS  current
        DESCRIPTION
        "This is a table of alarm log entries."
        INDEX {rx1plus1EventLogIndex}
        ::= { rx1plus1EventLogTable 1 }

Rx1plus1EventLogEntry ::= SEQUENCE {
        rx1plus1EventLogIndex                Integer32,
        rx1plus1EventLogAlarm                DisplayString
}

rx1plus1EventLogIndex OBJECT-TYPE
        SYNTAX  Integer32 (1..1000)
        MAX-ACCESS      not-accessible
        STATUS  current
        DESCRIPTION
        "Index to the table."
        ::= { rx1plus1EventLogEntry 1 }

rx1plus1EventLogAlarm OBJECT-TYPE
        SYNTAX  DisplayString
        MAX-ACCESS      read-only
        STATUS  current
        DESCRIPTION
        "The value of this object identifies this
        alarm log entry's alarm."
        ::= { rx1plus1EventLogEntry 2 }

--
-- StatsLog Subtree
--

rx1plus1ClearStatLog OBJECT-TYPE
        SYNTAX  NoYesValue
        MAX-ACCESS      read-write
        STATUS  current
        DESCRIPTION
        "The value of this object causes the RX to clear
        its statistics history."
        ::= { rx1plus1StatLog 1 }

rx1plus1StatLogInterval OBJECT-TYPE
        SYNTAX  Integer32 (1..1440)
        MAX-ACCESS      read-write
        STATUS  current
        DESCRIPTION
        "Statistics collection interval
		1 minute to 1440 minutes."
        ::= { rx1plus1StatLog 2 }
		
rx1plus1StatLogTable OBJECT-TYPE
        SYNTAX  SEQUENCE OF Rx1plus1StatLogEntry
        MAX-ACCESS      not-accessible
        STATUS  current
        DESCRIPTION
        "This is a table of statistics log entries."
        ::= { rx1plus1StatLog 3 }

rx1plus1StatLogEntry OBJECT-TYPE
        SYNTAX  Rx1plus1StatLogEntry
        MAX-ACCESS      not-accessible
        STATUS  current
        DESCRIPTION
        "This is a table of statistics log entries."
        INDEX {rx1plus1StatLogIndex}
        ::= { rx1plus1StatLogTable 1 }

Rx1plus1StatLogEntry ::= SEQUENCE {
        rx1plus1StatLogIndex                Integer32,
        rx1plus1StatLogAlarm                DisplayString
}

rx1plus1StatLogIndex OBJECT-TYPE
        SYNTAX  Integer32 (1..1000)
        MAX-ACCESS      not-accessible
        STATUS  current
        DESCRIPTION
        "Index to the table."
        ::= { rx1plus1StatLogEntry 1 }

rx1plus1StatLogAlarm OBJECT-TYPE
        SYNTAX  DisplayString
        MAX-ACCESS      read-only
        STATUS  current
        DESCRIPTION
        "The value of this object identifies above
		statistics entry.
		Format:
		date time Pout Pin Temperature DRO Volts Amps 10MHz
		Example:
		01/01/2000 09:08:23 47.5 -35.9 25 5.5 48.0 2.5 -10.8"
        ::= { rx1plus1StatLogEntry 2 }
		
		
--
-- Notifications
--		
rx1plus1EventsV2	OBJECT IDENTIFIER ::= { rx1plus1Events 0 }

rx1plus1RebootEvent NOTIFICATION-TYPE
	OBJECTS { 
		sysName
	}
	STATUS current
	DESCRIPTION
	"The trap is issued on cold or warm startup of firmware."
	::= {rx1plus1EventsV2 1}

rx1plus1InputThresholdALowMajorEvent NOTIFICATION-TYPE
	STATUS current
	DESCRIPTION
	"The trap is issued if the input level for LNB A drops below
	the configured threshold and the alarm is configured as a major."
	::= {rx1plus1EventsV2 2}

rx1plus1InputThresholdALowMinorEvent NOTIFICATION-TYPE
	STATUS current
	DESCRIPTION
	"The trap is issued if the input level for LNB A drops below
	the configured threshold and the alarm is configured as a minor."
	::= {rx1plus1EventsV2 3}

rx1plus1InputThresholdALowClearEvent NOTIFICATION-TYPE
	STATUS current
	DESCRIPTION
	"This trap is issued in response to a previous alarm clearing."
	::= {rx1plus1EventsV2 4}

rx1plus1InputThresholdBLowMajorEvent NOTIFICATION-TYPE
	STATUS current
	DESCRIPTION
	"The trap is issued if the input level for LNB B drops below
	the configured threshold and the alarm is configured as a major."
	::= {rx1plus1EventsV2 5}

rx1plus1InputThresholdBLowMinorEvent NOTIFICATION-TYPE
	STATUS current
	DESCRIPTION
	"The trap is issued if the input level for LNB B drops below
	the configured threshold and the alarm is configured as a minor."
	::= {rx1plus1EventsV2 6}

rx1plus1InputThresholdBLowClearEvent NOTIFICATION-TYPE
	STATUS current
	DESCRIPTION
	"This trap is issued in response to a previous alarm clearing."
	::= {rx1plus1EventsV2 7}

rx1plus110MHzMinorEvent NOTIFICATION-TYPE
	STATUS current
	DESCRIPTION
	"This trap is issued when the 10MHz level falls below the
	threshold."
	::= {rx1plus1EventsV2 8}

rx1plus110MHzClearEvent NOTIFICATION-TYPE
	STATUS current
	DESCRIPTION
	"This trap is issued in response to a previous alarm clearing."
	::= {rx1plus1EventsV2 9}

rx1plus1RxSimulatedAMajorEvent NOTIFICATION-TYPE
	STATUS current
	DESCRIPTION
	"This trap is issued when the user configures a simulated
	fault on the A side."
	::= {rx1plus1EventsV2 10}

rx1plus1RxSimulatedAClearEvent NOTIFICATION-TYPE
	STATUS current
	DESCRIPTION
	"This trap is issued in response to a previous alarm clearing."
	::= {rx1plus1EventsV2 11}

rx1plus1RxSimulatedBMajorEvent NOTIFICATION-TYPE
	STATUS current
	DESCRIPTION
	"This trap is issued when the user configures a simulated
	fault on the B side."
	::= {rx1plus1EventsV2 12}

rx1plus1RxSimulatedBClearEvent NOTIFICATION-TYPE
	STATUS current
	DESCRIPTION
	"This trap is issued in response to a previous alarm clearing."
	::= {rx1plus1EventsV2 13}

rx1plus1VdcLowAThresholdMajorEvent NOTIFICATION-TYPE
	STATUS current
	DESCRIPTION
	"This trap is issued when the LNB A voltage level fails below
	the configured threshold and configured as a major."
	::= {rx1plus1EventsV2 14}

rx1plus1VdcLowAThresholdMinorEvent NOTIFICATION-TYPE
	STATUS current
	DESCRIPTION
	"This trap is issued when the LNB A voltage level fails below
	the configured threshold and configured as a minor."
	::= {rx1plus1EventsV2 15}

rx1plus1VdcLowAThresholdClearEvent NOTIFICATION-TYPE
	STATUS current
	DESCRIPTION
	"This trap is issued in response to a previous alarm clearing."
	::= {rx1plus1EventsV2 16}

rx1plus1VdcLowBThresholdMajorEvent NOTIFICATION-TYPE
	STATUS current
	DESCRIPTION
	"This trap is issued when the LNB B voltage level fails below
	the configured threshold and configured as a major."
	::= {rx1plus1EventsV2 17}

rx1plus1VdcLowBThresholdMinorEvent NOTIFICATION-TYPE
	STATUS current
	DESCRIPTION
	"This trap is issued when the LNB B voltage level fails below
	the configured threshold and configured as a minor."
	::= {rx1plus1EventsV2 18}

rx1plus1VdcLowBThresholdClearEvent NOTIFICATION-TYPE
	STATUS current
	DESCRIPTION
	"This trap is issued in response to a previous alarm clearing."
	::= {rx1plus1EventsV2 19}

rx1plus1VdcHighAThresholdMajorEvent NOTIFICATION-TYPE
	STATUS current
	DESCRIPTION
	"This trap is issued when the LNB A voltage level rises above
	the configured threshold and configured as a major."
	::= {rx1plus1EventsV2 20}

rx1plus1VdcHighAThresholdMinorEvent NOTIFICATION-TYPE
	STATUS current
	DESCRIPTION
	"This trap is issued when the LNB A voltage level rises above
	the configured threshold and configured as a minor."
	::= {rx1plus1EventsV2 21}

rx1plus1VdcHighAThresholdClearEvent NOTIFICATION-TYPE
	STATUS current
	DESCRIPTION
	"This trap is issued in response to a previous alarm clearing."
	::= {rx1plus1EventsV2 22}

rx1plus1VdcHighBThresholdMajorEvent NOTIFICATION-TYPE
	STATUS current
	DESCRIPTION
	"This trap is issued when the LNB B voltage level rises above
	the configured threshold and configured as a major."
	::= {rx1plus1EventsV2 23}

rx1plus1VdcHighBThresholdMinorEvent NOTIFICATION-TYPE
	STATUS current
	DESCRIPTION
	"This trap is issued when the LNB B voltage level rises above
	the configured threshold and configured as a minor."
	::= {rx1plus1EventsV2 24}

rx1plus1VdcHighBThresholdClearEvent NOTIFICATION-TYPE
	STATUS current
	DESCRIPTION
	"This trap is issued in response to a previous alarm clearing."
	::= {rx1plus1EventsV2 25}

rx1plus1IdcLowAThresholdMajorEvent NOTIFICATION-TYPE
	STATUS current
	DESCRIPTION
	"This trap is issued when the LNB A current level falls below
	the configured threshold and configured as a major."
	::= {rx1plus1EventsV2 26}

rx1plus1IdcLowAThresholdMinorEvent NOTIFICATION-TYPE
	STATUS current
	DESCRIPTION
	"This trap is issued when the LNB A current level falls below
	the configured threshold and configured as a minor."
	::= {rx1plus1EventsV2 27}

rx1plus1IdcLowAThresholdClearEvent NOTIFICATION-TYPE
	STATUS current
	DESCRIPTION
	"This trap is issued in response to a previous alarm clearing."
	::= {rx1plus1EventsV2 28}

rx1plus1IdcLowBThresholdMajorEvent NOTIFICATION-TYPE
	STATUS current
	DESCRIPTION
	"This trap is issued when the LNB B current level falls below
	the configured threshold and configured as a major."
	::= {rx1plus1EventsV2 29}

rx1plus1IdcLowBThresholdMinorEvent NOTIFICATION-TYPE
	STATUS current
	DESCRIPTION
	"This trap is issued when the LNB B current level falls below
	the configured threshold and configured as a minor."
	::= {rx1plus1EventsV2 30}

rx1plus1IdcLowBThresholdClearEvent NOTIFICATION-TYPE
	STATUS current
	DESCRIPTION
	"This trap is issued in response to a previous alarm clearing."
	::= {rx1plus1EventsV2 31}

rx1plus1IdcHighAThresholdMajorEvent NOTIFICATION-TYPE
	STATUS current
	DESCRIPTION
	"This trap is issued when the LNB A current level rises above
	the configured threshold and configured as a major."
	::= {rx1plus1EventsV2 32}

rx1plus1IdcHighAThresholdMinorEvent NOTIFICATION-TYPE
	STATUS current
	DESCRIPTION
	"This trap is issued when the LNB A current level rises above
	the configured threshold and configured as a minor."
	::= {rx1plus1EventsV2 33}

rx1plus1IdcHighAThresholdClearEvent NOTIFICATION-TYPE
	STATUS current
	DESCRIPTION
	"This trap is issued in response to a previous alarm clearing."
	::= {rx1plus1EventsV2 34}

rx1plus1IdcHighBThresholdMajorEvent NOTIFICATION-TYPE
	STATUS current
	DESCRIPTION
	"This trap is issued when the LNB B current level rises above
	the configured threshold and configured as a major."
	::= {rx1plus1EventsV2 35}

rx1plus1IdcHighBThresholdMinorEvent NOTIFICATION-TYPE
	STATUS current
	DESCRIPTION
	"This trap is issued when the LNB B current level rises above
	the configured threshold and configured as a minor."
	::= {rx1plus1EventsV2 36}

rx1plus1IdcHighBThresholdClearEvent NOTIFICATION-TYPE
	STATUS current
	DESCRIPTION
	"This trap is issued in response to a previous alarm clearing."
	::= {rx1plus1EventsV2 37}

rx1plus1EmergencyOverrideOnEvent NOTIFICATION-TYPE
	STATUS current
	DESCRIPTION
	"This trap is issued when the emergency override switch is 
	place in the override position."
	::= {rx1plus1EventsV2 38}

rx1plus1EmergencyOverrideOffEvent NOTIFICATION-TYPE
	STATUS current
	DESCRIPTION
	"This trap is issued when the emergency override switch is 
	configured not to override."
	::= {rx1plus1EventsV2 39}

rx1plus1SwitchFaultMajorEvent NOTIFICATION-TYPE
	STATUS current
	DESCRIPTION
	"This trap is issued if the position of the waveguide switch
	cannot be determined."
	::= {rx1plus1EventsV2 40}

rx1plus1SwitchFaultClearEvent NOTIFICATION-TYPE
	STATUS current
	DESCRIPTION
	"This trap is issued in response to a previous alarm clearing."
	::= {rx1plus1EventsV2 41}

--
-- Compliances		
--

rx1plus1ComplianceV1  MODULE-COMPLIANCE
        STATUS     current
        DESCRIPTION 
                "The compliance statement starting with firmware
				revision 0.89."
        MODULE
                MANDATORY-GROUPS { 
                        rx1plus1CfgGroup,
						rx1plus1ControlGroup,
						rx1plus1StatusGroup,
						rx1plus1NotificationV0dot11Group
                } 
        ::= { rx1plus1Compliances 1 }

rx1plus1ComplianceV2  MODULE-COMPLIANCE
        STATUS     current
        DESCRIPTION 
                "The compliance statement starting with firmware
				revision 5.00."
        MODULE
                MANDATORY-GROUPS { 
                        rx1plus1CfgGroup,
						rx1plus1CfgV2Group,
						rx1plus1ControlGroup,
						rx1plus1StatusGroup,
						rx1plus1StatusV2Group,
						rx1plus1NotificationV0dot11Group
                } 
        ::= { rx1plus1Compliances 2 }
		
--
-- Group definitions
--
		
rx1plus1CfgGroup OBJECT-GROUP
	OBJECTS {
		rx1plus1IPAddress, rx1plus1IPGateway,
		rx1plus1IPSubnet, rx1plus1IPTelnetPort,
		rx1plus1RS485Address, rx1plus1RS485Baudrate,
		rx1plus1RS485Delay,	rx1plus1InputLowThresholdSuppressibleA,
		rx1plus1InputLowThresholdSuppressibleB,	rx1plus1VDCLowThresholdSuppressibleA,
		rx1plus1VDCLowThresholdSuppressibleB, rx1plus1VDCHighThresholdSuppressibleA,
		rx1plus1VDCHighThresholdSuppressibleB, rx1plus1IDCLowThresholdSuppressibleA,
		rx1plus1IDCLowThresholdSuppressibleB, rx1plus1IDCHighThresholdSuppressibleA,
		rx1plus1IDCHighThresholdSuppressibleB, rx1plus1InputLowThresholdAlarmLevelA,
		rx1plus1InputLowThresholdAlarmLevelB, rx1plus1VDCLowThresholdAlarmLevelA,
		rx1plus1VDCLowThresholdAlarmLevelB, rx1plus1VDCHighThresholdAlarmLevelA,
		rx1plus1VDCHighThresholdAlarmLevelB, rx1plus1IDCLowThresholdAlarmLevelA,
		rx1plus1IDCLowThresholdAlarmLevelB, rx1plus1IDCHighThresholdAlarmLevelA,
		rx1plus1IDCHighThresholdAlarmLevelB, rx1plus110MHzAlarm,
		rx1plus1VerboseMode, rx1plus1Echo,
		rx1plus1PasswordTimeOut, rx1plus1WebServerRefresh,
		rx1plus1InputThresholdLowA, rx1plus1InputThresholdLowB,
		rx1plus1VDCHighThresholdA, rx1plus1VDCHighThresholdB,
		rx1plus1VDCLowThresholdA, rx1plus1VDCLowThresholdB,
		rx1plus1IDCHighThresholdA, rx1plus1IDCHighThresholdB,
		rx1plus1IDCLowThresholdA, rx1plus1IDCLowThresholdB,
		rx1plus1RedundancyMode,	rx1plus1SwitchingType,
		rx1plus1SwitchPosition,	rx1plus1SystemStatus
	}
	STATUS		current
	DESCRIPTION
	"The collection of objects which are used to provide
	the RX1+1 configuration parameters."
	::= {  rx1plus1Groups 1 }

rx1plus1ControlGroup OBJECT-GROUP
	OBJECTS {
		rx1plus1SuppressAlarmsA, rx1plus1SuppressAlarmsB,
		rx1plus1SimulateAlarmA, rx1plus1SimulateAlarmB,
		rx1plus1ClearAlarmLog, rx1plus1FirmwareReboot
	}
	STATUS		current
	DESCRIPTION
	"The collection of objects which are used to provide
	the RX1+1 control parameters."
	::= {  rx1plus1Groups 2 }

rx1plus1StatusGroup OBJECT-GROUP
	OBJECTS {
		rx1plus1ModelNumber, rx1plus1SerialNumber,
		rx1plus1FirmwareVersion, rx1plus1InputThresholdALow,
		rx1plus1InputThresholdBLow, rx1plus110MHz,
		rx1plus1RxSimulatedA, rx1plus1RxSimulatedB,
		rx1plus1VdcLowAThreshold, rx1plus1VdcLowBThreshold,
		rx1plus1VdcHighAThreshold, rx1plus1VdcHighBThreshold,
		rx1plus1IdcLowAThreshold, rx1plus1IdcLowBThreshold,
		rx1plus1IdcHighAThreshold, rx1plus1IdcHighBThreshold,
		rx1plus1EmergencyOverride, rx1plus1SwitchFault,
		rx1plus1LogAlignError, rx1plus1CfgDataError,
		rx1plus1EthernetDownload, rx1plus1SerialDownload,
		rx1plus1FWReboot, rx1plus1DCVoltageA,
		rx1plus1DCVoltageB, rx1plus1DCCurrentA,
		rx1plus1DCCurrentB,	rx1plus1InputPowerLevelA,
		rx1plus1InputPowerLevelB, rx1plus1AlarmLogNumber,
		rx1plus1AlarmLogType, rx1plus1AlarmLogAlarms,
		rx1plus1TenMegLevel
	}
	STATUS		current
	DESCRIPTION
	"The collection of objects which are used to provide
	the RX1+1 status information."
	::= {  rx1plus1Groups 3 }

rx1plus1NotificationV0dot11Group NOTIFICATION-GROUP
	NOTIFICATIONS {
		rx1plus1RebootEvent,
		rx1plus1InputThresholdALowMajorEvent,
		rx1plus1InputThresholdALowMinorEvent,
		rx1plus1InputThresholdALowClearEvent,
		rx1plus1InputThresholdBLowMajorEvent,
		rx1plus1InputThresholdBLowMinorEvent,
		rx1plus1InputThresholdBLowClearEvent,
		rx1plus110MHzMinorEvent,
		rx1plus110MHzClearEvent,
		rx1plus1RxSimulatedAMajorEvent,
		rx1plus1RxSimulatedAClearEvent,
		rx1plus1RxSimulatedBMajorEvent,
		rx1plus1RxSimulatedBClearEvent,
		rx1plus1VdcLowAThresholdMajorEvent,
		rx1plus1VdcLowAThresholdMinorEvent,
		rx1plus1VdcLowAThresholdClearEvent,
		rx1plus1VdcLowBThresholdMajorEvent,
		rx1plus1VdcLowBThresholdMinorEvent,
		rx1plus1VdcLowBThresholdClearEvent,
		rx1plus1VdcHighAThresholdMajorEvent,
		rx1plus1VdcHighAThresholdMinorEvent,
		rx1plus1VdcHighAThresholdClearEvent,
		rx1plus1VdcHighBThresholdMajorEvent,
		rx1plus1VdcHighBThresholdMinorEvent,
		rx1plus1VdcHighBThresholdClearEvent,
		rx1plus1IdcLowAThresholdMajorEvent,
		rx1plus1IdcLowAThresholdMinorEvent,
		rx1plus1IdcLowAThresholdClearEvent,
		rx1plus1IdcLowBThresholdMajorEvent,
		rx1plus1IdcLowBThresholdMinorEvent,
		rx1plus1IdcLowBThresholdClearEvent,
		rx1plus1IdcHighAThresholdMajorEvent,
		rx1plus1IdcHighAThresholdMinorEvent,
		rx1plus1IdcHighAThresholdClearEvent,
		rx1plus1IdcHighBThresholdMajorEvent,
		rx1plus1IdcHighBThresholdMinorEvent,
		rx1plus1IdcHighBThresholdClearEvent,
		rx1plus1EmergencyOverrideOnEvent,
		rx1plus1EmergencyOverrideOffEvent,
		rx1plus1SwitchFaultMajorEvent,
		rx1plus1SwitchFaultClearEvent
	}
	STATUS		current
	DESCRIPTION
	"The notifier group starting with 0.11 firmware."
	::= {  rx1plus1Groups 4 }

rx1plus1StatusV2Group OBJECT-GROUP
	OBJECTS {
		rx1plus1HardwareVersion,
		rx1plus1SupplyVoltRange,
		rx1plus1Provider,
		rx1plus1EventLogAlarm,
		rx1plus1ClearStatLog,
		rx1plus1StatLogInterval,
		rx1plus1StatLogAlarm,
		rx1plus1Internal10MHz1
	}
	STATUS		current
	DESCRIPTION
	"Additional status objects."
	::= {  rx1plus1Groups 5 }

rx1plus1CfgV2Group OBJECT-GROUP
	OBJECTS {
		rx1plus1RealTimeClock,
		rx1plus1NtpIpAddr,
		rx1plus1TimezoneOffset,
		rx1plus1WebPageTitle,
		rx1plus1BandVolts,
		rx1plus1Band22khz,
		rx1plus1Trim10mhz1,
		rx1plus1Trim10mhz2,
		rx1plus1TenMHzEnable,
		rx1plus1RS485Mode
	}
	STATUS		current
	DESCRIPTION
	"The collection of objects which are used to provide
	the RX1+1 configuration parameters."
	::= {  rx1plus1Groups 6 }
	
END
