TERRASAT-PAA-MIB DEFINITIONS ::= BEGIN

IMPORTS
        terrasat                
                FROM TERRASAT-SMI-MIB
        OBJECT-GROUP, MODULE-COMPLIANCE
                FROM SNMPv2-CONF
        AlarmState
                FROM TERRASAT-TC-MIB
        OBJECT-TYPE, MODULE-IDENTITY, Integer32
                FROM SNMPv2-SMI
        DisplayString
                FROM SNMPv2-TC;

paaMIB MODULE-IDENTITY
    LAST-UPDATED    "202108100000Z"
    ORGANIZATION    "Terrasat Communications, Inc."
    CONTACT-INFO
            "Terrasat Communications
            Customer Service

            Address: 315 Digital Drive
            Morgan Hill, CA  95037
            USA

            Tel: +1 408 782-2166

            E-mail: techsupport@terrasatinc.com"
    DESCRIPTION
        "The management MIB for PAA(x2) used on the 
		phase combined systems."

        REVISION        "202108100000Z"
        DESCRIPTION
                "The initial version."
    ::= { terrasat 7 }


paaInfo			OBJECT IDENTIFIER ::= { paaMIB 1 }
paaAlarm		OBJECT IDENTIFIER ::= { paaMIB 2 }
paaSensor		OBJECT IDENTIFIER ::= { paaMIB 3 }
paaTx			OBJECT IDENTIFIER ::= { paaMIB 4 }

paaGroups		OBJECT IDENTIFIER ::= { paaMIB 10 }
paaCompliances	OBJECT IDENTIFIER ::= { paaMIB 11 }


--
-- The Info Group
--

-- 1.3.6.1.4.1.21369.7.1.1
paaModelNumberA OBJECT-TYPE
        SYNTAX  DisplayString
        MAX-ACCESS      read-only
        STATUS  current
        DESCRIPTION
        "Model Number of the A PAA. This matches the label on PAA Housing"
        ::= { paaInfo 1 }

-- 1.3.6.1.4.1.21369.7.1.2
paaModelNumberB OBJECT-TYPE
        SYNTAX  DisplayString
        MAX-ACCESS      read-only
        STATUS  current
        DESCRIPTION
        "Model Number of the B PAA. This matches the label on PAA Housing"
        ::= { paaInfo 2 }

-- 1.3.6.1.4.1.21369.7.1.3
paaSerialNumberA OBJECT-TYPE
        SYNTAX  DisplayString
        MAX-ACCESS      read-only
        STATUS  current
        DESCRIPTION
        "Serial Number of the A PAA. This matches the label on the PAA Housing"
        ::= { paaInfo 3 }

-- 1.3.6.1.4.1.21369.7.1.4
paaSerialNumberB OBJECT-TYPE
        SYNTAX  DisplayString
        MAX-ACCESS      read-only
        STATUS  current
        DESCRIPTION
        "Serial Number of the B PAA. This matches the label on the PAA Housing"
        ::= { paaInfo 4 }

-- 1.3.6.1.4.1.21369.7.1.5
paaFirmwareVersionA OBJECT-TYPE
        SYNTAX  DisplayString
        MAX-ACCESS      read-only
        STATUS  current
        DESCRIPTION
        "Firmware version installed in the A PAA."
        ::= { paaInfo 5 }

-- 1.3.6.1.4.1.21369.7.1.6
paaFirmwareVersionB OBJECT-TYPE
        SYNTAX  DisplayString
        MAX-ACCESS      read-only
        STATUS  current
        DESCRIPTION
        "Firmware version installed in the B PAA."
        ::= { paaInfo 6 }

-- 1.3.6.1.4.1.21369.7.1.7
paaHardwareVersionA OBJECT-TYPE
        SYNTAX  DisplayString
        MAX-ACCESS      read-only
        STATUS  current
        DESCRIPTION
        "Hardware version of the A PAA."
        ::= { paaInfo 7 }

-- 1.3.6.1.4.1.21369.7.1.8
paaHardwareVersionB OBJECT-TYPE
        SYNTAX  DisplayString
        MAX-ACCESS      read-only
        STATUS  current
        DESCRIPTION
        "Hardware version of the B PAA."
        ::= { paaInfo 8 }

-- 1.3.6.1.4.1.21369.7.1.9
paaTotalSystemHoursA OBJECT-TYPE
        SYNTAX  Integer32
        MAX-ACCESS      read-only
        STATUS  current
        DESCRIPTION
        "Total hours the A PAA has been powered up."
        ::= { paaInfo 9 }

-- 1.3.6.1.4.1.21369.7.1.10
paaTotalSystemHoursB OBJECT-TYPE
        SYNTAX  Integer32
        MAX-ACCESS      read-only
        STATUS  current
        DESCRIPTION
        "Total hours the B PAA has been powered up."
        ::= { paaInfo 10 }

-- 1.3.6.1.4.1.21369.7.1.11
paaTotalTxHoursA OBJECT-TYPE
        SYNTAX  Integer32
        MAX-ACCESS      read-only
        STATUS  current
        DESCRIPTION
        "Total hours the A PAA has been able to transmit."
        ::= { paaInfo 11 }

-- 1.3.6.1.4.1.21369.7.1.12
paaTotalTxHoursB OBJECT-TYPE
        SYNTAX  Integer32
        MAX-ACCESS      read-only
        STATUS  current
        DESCRIPTION
        "Total hours the B PAA has been able to transmit."
        ::= { paaInfo 12 }

--
-- The Alarm Group
--

-- 1.3.6.1.4.1.21369.7.2.1
paaTxOutputA OBJECT-TYPE
        SYNTAX  AlarmState
        MAX-ACCESS      read-only
        STATUS  current
        DESCRIPTION
        "Tx Output A alarm.    
		(0) No Alarm
        (1) Alarm
        (2) Informational
        (3) Minor
        (4) Major
		"
        ::= { paaAlarm 1 }

-- 1.3.6.1.4.1.21369.7.2.2
paaTxOutputB OBJECT-TYPE
        SYNTAX  AlarmState
        MAX-ACCESS      read-only
        STATUS  current
        DESCRIPTION
        "Tx Output B alarm.    
		(0) No Alarm
        (1) Alarm
        (2) Informational
        (3) Minor
        (4) Major
		"
        ::= { paaAlarm 2 }

-- 1.3.6.1.4.1.21369.7.2.3
paaTxOutputLowA OBJECT-TYPE
        SYNTAX  AlarmState
        MAX-ACCESS      read-only
        STATUS  current
        DESCRIPTION
        "Tx Output threshold low A alarm.    
		(0) No Alarm
        (1) Alarm
        (2) Informational
        (3) Minor
        (4) Major
		"
        ::= { paaAlarm 3 }

-- 1.3.6.1.4.1.21369.7.2.4
paaTxOutputLowB OBJECT-TYPE
        SYNTAX  AlarmState
        MAX-ACCESS      read-only
        STATUS  current
        DESCRIPTION
        "Tx Output threshold low B alarm.    
		(0) No Alarm
        (1) Alarm
        (2) Informational
        (3) Minor
        (4) Major
		"
        ::= { paaAlarm 4 }
		
-- 1.3.6.1.4.1.21369.7.2.5
paaTxOutputHighA OBJECT-TYPE
        SYNTAX  AlarmState
        MAX-ACCESS      read-only
        STATUS  current
        DESCRIPTION
        "Tx Output threshold high A alarm.    
		(0) No Alarm
        (1) Alarm
        (2) Informational
        (3) Minor
        (4) Major
		"
        ::= { paaAlarm 5 }

-- 1.3.6.1.4.1.21369.7.2.6
paaTxOutputHighB OBJECT-TYPE
        SYNTAX  AlarmState
        MAX-ACCESS      read-only
        STATUS  current
        DESCRIPTION
        "Tx Output threshold high B alarm.    
		(0) No Alarm
        (1) Alarm
        (2) Informational
        (3) Minor
        (4) Major
		"
        ::= { paaAlarm 6 }
		
-- 1.3.6.1.4.1.21369.7.2.7
paaTxInputLowA OBJECT-TYPE
        SYNTAX  AlarmState
        MAX-ACCESS      read-only
        STATUS  current
        DESCRIPTION
        "Tx input threshold low A alarm.    
		(0) No Alarm
        (1) Alarm
        (2) Informational
        (3) Minor
        (4) Major
		"
        ::= { paaAlarm 7 }

-- 1.3.6.1.4.1.21369.7.2.8
paaTxInputLowB OBJECT-TYPE
        SYNTAX  AlarmState
        MAX-ACCESS      read-only
        STATUS  current
        DESCRIPTION
        "Tx input threshold low B alarm.    
		(0) No Alarm
        (1) Alarm
        (2) Informational
        (3) Minor
        (4) Major
		"
        ::= { paaAlarm 8 }
		
-- 1.3.6.1.4.1.21369.7.2.9
paaTxInputHighA OBJECT-TYPE
        SYNTAX  AlarmState
        MAX-ACCESS      read-only
        STATUS  current
        DESCRIPTION
        "Tx input threshold high A alarm.    
		(0) No Alarm
        (1) Alarm
        (2) Informational
        (3) Minor
        (4) Major
		"
        ::= { paaAlarm 9 }

-- 1.3.6.1.4.1.21369.7.2.10
paaTxInputHighB OBJECT-TYPE
        SYNTAX  AlarmState
        MAX-ACCESS      read-only
        STATUS  current
        DESCRIPTION
        "Tx input threshold high B alarm.    
		(0) No Alarm
        (1) Alarm
        (2) Informational
        (3) Minor
        (4) Major
		"
        ::= { paaAlarm 10 }
		
-- 1.3.6.1.4.1.21369.7.2.11
paaTemperatureA OBJECT-TYPE
        SYNTAX  AlarmState
        MAX-ACCESS      read-only
        STATUS  current
        DESCRIPTION
        "Internal temperature A alarm.    
		(0) No Alarm
        (1) Alarm
        (2) Informational
        (3) Minor
        (4) Major
		"
        ::= { paaAlarm 11 }

-- 1.3.6.1.4.1.21369.7.2.12
paaTemperatureB OBJECT-TYPE
        SYNTAX  AlarmState
        MAX-ACCESS      read-only
        STATUS  current
        DESCRIPTION
        "Internal temperature B alarm.    
		(0) No Alarm
        (1) Alarm
        (2) Informational
        (3) Minor
        (4) Major
		"
        ::= { paaAlarm 12 }

--
-- The Sensor Group
--

-- 1.3.6.1.4.1.21369.7.3.1
paaSupplyVoltageA OBJECT-TYPE
        SYNTAX	Integer32
		UNITS	"d-1"
        MAX-ACCESS	read-only
        STATUS	current
        DESCRIPTION
        "Power supply voltage A. Divide by 10 to convert
		to floating point."
        ::= { paaSensor 1 }

-- 1.3.6.1.4.1.21369.7.3.2
paaSupplyVoltageB OBJECT-TYPE
        SYNTAX	Integer32
		UNITS	"d-1"
        MAX-ACCESS	read-only
        STATUS	current
        DESCRIPTION
        "Power supply voltage B. Divide by 10 to convert
		to floating point."
        ::= { paaSensor 2 }

-- 1.3.6.1.4.1.21369.7.3.3
paaSupplyCurrentA OBJECT-TYPE
        SYNTAX	Integer32
		UNITS	"d-1"
        MAX-ACCESS	read-only
        STATUS	current
        DESCRIPTION
        "Power supply current A. Divide by 10 to convert
		to floating point."
        ::= { paaSensor 3 }

-- 1.3.6.1.4.1.21369.7.3.4
paaSupplyCurrentB OBJECT-TYPE
        SYNTAX	Integer32
		UNITS	"d-1"
        MAX-ACCESS	read-only
        STATUS	current
        DESCRIPTION
        "Power supply current B. Divide by 10 to convert
		to floating point."
        ::= { paaSensor 4 }

-- 1.3.6.1.4.1.21369.7.3.5
paaSupplyWattA OBJECT-TYPE
        SYNTAX	Integer32
        MAX-ACCESS	read-only
        STATUS	current
        DESCRIPTION
        "Power supply watts A rounded to the nearest watt."
        ::= { paaSensor 5 }

-- 1.3.6.1.4.1.21369.7.3.6
paaSupplyWattB OBJECT-TYPE
        SYNTAX	Integer32
        MAX-ACCESS	read-only
        STATUS	current
        DESCRIPTION
        "Power supply watts B rounded to the nearest watt."
        ::= { paaSensor 6 }

-- 1.3.6.1.4.1.21369.7.3.7
paaTxInputLevelA OBJECT-TYPE
        SYNTAX	Integer32
		UNITS	"d-1"
        MAX-ACCESS	read-only
        STATUS	current
        DESCRIPTION
        "Tx input level dBm A. Divide by 10 to convert
		to floating point."
        ::= { paaSensor 7 }

-- 1.3.6.1.4.1.21369.7.3.8
paaTxInputLevelB OBJECT-TYPE
        SYNTAX	Integer32
		UNITS	"d-1"
        MAX-ACCESS	read-only
        STATUS	current
        DESCRIPTION
        "Tx input level dBm B. Divide by 10 to convert
		to floating point."
        ::= { paaSensor 8 }

-- 1.3.6.1.4.1.21369.7.3.9
paaTxOutputLevelA OBJECT-TYPE
        SYNTAX	Integer32
		UNITS	"d-1"
        MAX-ACCESS	read-only
        STATUS	current
        DESCRIPTION
        "Tx output level dBm A. Divide by 10 to convert
		to floating point."
        ::= { paaSensor 9 }

-- 1.3.6.1.4.1.21369.7.3.10
paaTxOutputLevelB OBJECT-TYPE
        SYNTAX	Integer32
		UNITS	"d-1"
        MAX-ACCESS	read-only
        STATUS	current
        DESCRIPTION
        "Tx output level dBm B. Divide by 10 to convert
		to floating point."
        ::= { paaSensor 10 }

-- 1.3.6.1.4.1.21369.7.3.11
paaInternalTemperatureA OBJECT-TYPE
        SYNTAX	Integer32
        MAX-ACCESS	read-only
        STATUS	current
        DESCRIPTION
        "PAA A internal temperature. Range is -62 to 104 degrees
		centigrade."
        ::= { paaSensor 11 }
		
-- 1.3.6.1.4.1.21369.7.3.12
paaInternalTemperatureB OBJECT-TYPE
        SYNTAX	Integer32
        MAX-ACCESS	read-only
        STATUS	current
        DESCRIPTION
        "PAA B internal temperature. Range is -62 to 104 degrees
		centigrade."
        ::= { paaSensor 12 }

--
-- The Tx Group
--

-- 1.3.6.1.4.1.21369.7.4.1
paaAttenuationA OBJECT-TYPE
        SYNTAX	Integer32
		UNITS	"d-1"
        MAX-ACCESS	read-write
        STATUS	current
        DESCRIPTION
        "PAA A attenuation -50 to +50.
		Range is -50(-5.0 dB) to +50(+5.0 dB)."
        ::= { paaTx 1 }

-- 1.3.6.1.4.1.21369.7.4.2
paaAttenuationB OBJECT-TYPE
        SYNTAX	Integer32
		UNITS	"d-1"
        MAX-ACCESS	read-write
        STATUS	current
        DESCRIPTION
        "PAA B attenuation -50 to +50.
		Range is -50(-5.0 dB) to +50(+5.0 dB)."
        ::= { paaTx 2 }

-- 1.3.6.1.4.1.21369.7.4.3
paaSamplePortCorrectionA OBJECT-TYPE
        SYNTAX	Integer32
		UNITS	"d-1"
        MAX-ACCESS	read-write
        STATUS	current
        DESCRIPTION
        "Sample port correction factor A. Divide by 10 to convert
		to floating point."
        ::= { paaTx 3 }

-- 1.3.6.1.4.1.21369.7.4.4
paaSamplePortCorrectionB OBJECT-TYPE
        SYNTAX	Integer32
		UNITS	"d-1"
        MAX-ACCESS	read-write
        STATUS	current
        DESCRIPTION
        "Sample port correction factor B. Divide by 10 to convert
		to floating point."
        ::= { paaTx 4 }

--
-- Group definitions
--
		
paaInfoGroup OBJECT-GROUP
        OBJECTS {
				paaModelNumberA,
				paaSerialNumberA,
				paaFirmwareVersionA,
				paaHardwareVersionA,
				paaTotalSystemHoursA,
				paaTotalTxHoursA,
				paaModelNumberB,
				paaSerialNumberB,
				paaFirmwareVersionB,
				paaHardwareVersionB,
				paaTotalSystemHoursB,
				paaTotalTxHoursB
        }
        STATUS          current
        DESCRIPTION
        "Information group for the PAA."
        ::= {  paaGroups 1 }

paaAlarmsGroup OBJECT-GROUP
        OBJECTS {
				paaTxOutputA,
				paaTxOutputLowA,
				paaTxOutputHighA,
				paaTxInputLowA,
				paaTxInputHighA,
				paaTemperatureA,
				paaTxOutputB,
				paaTxOutputLowB,
				paaTxOutputHighB,
				paaTxInputLowB,
				paaTxInputHighB,
				paaTemperatureB
        }
        STATUS          current
        DESCRIPTION
        "Alarms for the PAA."
        ::= {  paaGroups 2 }

paaSensorGroup OBJECT-GROUP
        OBJECTS {
				paaSupplyVoltageA,
				paaSupplyCurrentA,
				paaSupplyWattA,
				paaTxInputLevelA,
				paaTxOutputLevelA,
				paaInternalTemperatureA,
				paaSupplyVoltageB,
				paaSupplyCurrentB,
				paaSupplyWattB,
				paaTxInputLevelB,
				paaTxOutputLevelB,
				paaInternalTemperatureB
        }
        STATUS          current
        DESCRIPTION
        "PAA sensors."
        ::= {  paaGroups 3 }

paaTxGroup OBJECT-GROUP
        OBJECTS {
				paaAttenuationA,
				paaSamplePortCorrectionA,
				paaAttenuationB,
				paaSamplePortCorrectionB
        }
        STATUS          current
        DESCRIPTION
        "PAA transmitter related."
        ::= {  paaGroups 4 }

--
-- Compliances		
--

paaCompliance  MODULE-COMPLIANCE
        STATUS     current
        DESCRIPTION 
                "The compliance statement for the PAA."
        MODULE
                MANDATORY-GROUPS { 
                        paaInfoGroup,
						paaAlarmsGroup,
						paaSensorGroup,
						paaTxGroup
                } 
        ::= { paaCompliances 1 }
				
END
