TERRASAT-SMI-MIB DEFINITIONS ::= BEGIN

IMPORTS
    MODULE-IDENTITY, enterprises
        FROM SNMPv2-SMI;

terrasat MODULE-IDENTITY
    LAST-UPDATED    "200909280000Z"
    ORGANIZATION    "Terrasat Communications, Inc."
    CONTACT-INFO
            "Terrasat Communications
            Customer Service

            Address: 235 Vineyard Court
            Morgan Hill, CA  95037
            USA

            Tel: +1 408 782-2166

            E-mail: techsupport@terrasatinc.com"
    DESCRIPTION
        "The Structure of Management Information for the
        Terrasat enterprise."
	REVISION	"200909280000Z"
	DESCRIPTION
		"The intial version."
    ::= { enterprises 21369 }

END
